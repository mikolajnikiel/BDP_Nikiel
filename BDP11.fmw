FME workspace BDP11.fmw

Parameters:
- email = .   # Email
- haslo =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   # Hasło
- email_klienta = .   # Email klienta
- powiat = powiat inowrocławski   # Nazwa powiatu
- pokrycie = 100   # Maksymalne pokrycie chmurami
- poczatek = 20230501   # Data początkowa
- koncowa = 20230504   # Data końcowa
- SourceDataset_SHAPEFILE = $(FME_MF_DIR)powiaty\powiaty.shp   # Source Esri Shapefile(s)

Readers:
- SHAPEFILE_1: SHAPEFILE from $(SourceDataset_SHAPEFILE)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> Tester
Tester
    BOOL_OP = OR
    TEST_CLAUSE = TEST $(powiat) = @Value(JPT_NAZWA_)
    TEST_MODE = TEST
    PASSED -> PythonCaller
    PASSED -> Reprojector
Reprojector
    DEST = UTM84-34N
    INTERPOLATION_TYPE = NearestNeighbor
    RASTER_CELL_SIZE = PreserveCells
    RASTER_TOLERANCE = 0.0
    REPROJECTED -> Clipper [CLIPPER]
PythonCaller
    INPUT_PORT_CONNECTED = CONNECTED
    PYTHONSOURCE:
      import fme
      from fme import BaseTransformer
      import fmeobjects
      import smtplib
      from datetime import datetime
      from email.mime.text import MIMEText

      class FeatureProcessor(object):
          def input(self, feature):

              email = fme.macroValues.get('email')
              email_klienta = fme.macroValues.get('email_klienta')
              powiat = fme.macroValues.get('powiat')
              data = datetime.now().strftime("%Y-%m-%d %H:%M:%S")
              msg_content = f"Drogi użytkowniku {email}, o godzinie {data} rozpoczęto przetwarzanie danych dla powiatu {powiat}"

              msg = MIMEText(msg_content)
              msg['Subject'] = "Start procesu FME"
              msg['From'] = email
              msg['To'] = email_klienta


              self.pyoutput(feature)
    PYTHONSYMBOL = FeatureProcessor
    -> SentinelDownloader [Initiator]
SentinelDownloader
    ALL_BANDS = NO
    ALL_BANDS_10 = NO
    ALL_BANDS_20 = NO
    ALL_BANDS_60 = NO
    B11_20m = NO
    B11_60m = NO
    B12_20m = NO
    B12_60m = NO
    B1_60m = NO
    B2_10m = NO
    B2_20m = NO
    B2_60m = NO
    B3_10m = NO
    B3_20m = NO
    B3_60m = NO
    B4_10m = YES
    B4_20m = NO
    B4_60m = NO
    B5_20m = NO
    B5_60m = NO
    B6_20m = NO
    B6_60m = NO
    B7_20m = NO
    B7_60m = NO
    B8_10m = YES
    B8_20m = NO
    B8_60m = NO
    B9_60m = NO
    BEGIN = 20230501
    CloudCover = $(pokrycie)
    END = $(koncowa)
    LEVEL = Level 2A
    MOST_RECENT = YES
    TCI_10m = NO
    TCI_20m = NO
    TCI_60m = YES
    WEB_CON = sentinel
    platform = Sentinel-2
    B04 -> RasterExpressionEvaluator [A]
    B08 -> RasterExpressionEvaluator [B]
RasterExpressionEvaluator
    ATTR_ACCUM_MODE = MERGE
    ATTR_CONFLICT_RES_LOOKUP = PREFER_B
    EXPRESSION_LIST = REAL64 (B[0]-A[0])/(B[0]+A[0])
    MODE = Two Rasters
    ATTR_CONFLICT_RES = Prefer B
    RESULT -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> GeometryFilter
GeometryFilter
    FILTER_MODE = SIMPLE
    FILTER_MULTI = FILTER_TYPES]Raster]FILTER_TYPES_Simple]Raster
    FILTER_TYPES = Raster
    FILTER_TYPES_Simple = Raster
    Raster -> RasterStatisticsCalculator
RasterStatisticsCalculator
    RASTER_LEVEL = BAND_ONLY
    RASTER_STATS = "0   MEAN   STDEV   "
    -> VariableSetter
VariableSetter
    SCOPE = Global
    VALUE = Srednia: @Value(band0.mean), Odchylenie: @Value(band0.stdev)
    VARNAME = ndvi_wynik
    -> RasterResampler
RasterResampler
    INTERPOLATION_TYPE = NearestNeighbor
    ROWCOL_OR_CELLSIZE = CellSize
    X_CELL_SIZE = 60
    Y_CELL_SIZE = 60
    INTERPOLATION_TYPE_NAME = Nearest Neighbor
    RESAMPLED -> FeatureWriter [Raster1]
FeatureWriter
    CONFIG_PARAMETERS = ESCAPE_COMMAS_IN_FTP_FORMAT_PARAMETERS,yes
    DATASET = $(FME_MF_DIR_ENCODED)cw11
    DATASET_ATTR = _dataset
    FEATURE_TYPE_LIST_ATTR = _feature_types
    FORMAT = GEOTIFF
    GEOTIFF_COORDINATE_SYSTEM_GRANULARITY = FEATURE
    GEOTIFF_DESTINATION_DATASETTYPE_VALIDATION = Yes
    GEOTIFF_FORMAT_ATTRIBUTES_OVERRIDE_FEATURE_TYPE_PARAMETERS = No
    GEOTIFF_IGNORE_RASTER_TYPE_KEY = No
    GEOTIFF_REPROJECTION_OPTIONS = No
    GEOTIFF_WRITE_ESRI_COMPATIBLE_COORDSYS = No
    GEOTIFF_WRITE_GEOGRAPHIC_COORDSYS_AS_EPSG_CODE = Yes
    GEOTIFF_WRITE_GEOGRAPHIC_KEYS_FOR_PROJECTED_COORDSYS = Yes
    GEOTIFF_WRITE_OFFSETS_IN_CS_UNITS = Yes
    GEOTIFF_WRITE_PROJECTED_COORDSYS_AS_EPSG_CODE = Yes
    TOTAL_FEATURES_WRITTEN_ATTR = _total_features_written
    SUMMARY -> ZipArchiver
ZipArchiver
    COMPRESSION_LEVEL = -1
    FILE_PATH = $(FME_MF_DIR_ENCODED)cw11\NDVI_powiat rzeszowski.tif.tif
    MODE = APPEND
    ZIP_PATH = $(FME_MF_DIR_ENCODED)cw11\NDVI_zzipowany.zip
    -> VariableRetriever
VariableRetriever
    SCOPE = Global
    VALUE_ATTR = _statystyki
    VARNAME = ndvi_wynik
    -> Decelerator
Decelerator
    DECEL_LOOKUP = PERFEATDELAY
    DELAY = 30
    DECEL_TYPE = Per Feature Delay
    -> PythonCaller_2
PythonCaller_2
    INPUT_PORT_CONNECTED = CONNECTED
    PYTHONSOURCE:
      import fme, fmeobjects, smtplib, os
      from email.mime.multipart import MIMEMultipart
      from email.mime.text import MIMEText
      from email.mime.base import MIMEBase
      from email import encoders

      class FeatureProcessor(object):
          def input(self, feature):
              klient = fme.macroValues.get('email_klienta')
              moj_mail = fme.macroValues.get('email')
              haslo = fme.macroValues.get('haslo')
              sciezka = r"$(FME_MF_DIR_ENCODED)cw11\NDVI_zzipowany.zip"
              stats = feature.getAttribute('_statystyki')
              msg = MIMEMultipart()
              msg['Subject'], msg['From'], msg['To'] = "Raport NDVI", moj_mail, klient
              msg.attach(MIMEText(f"Wyniki: {stats}", 'plain'))
              if os.path.exists(sciezka):
                  with open(sciezka, "rb") as f:
                      part = MIMEBase("application", "zip")
                      part.set_payload(f.read())
                  encoders.encode_base64(part)
                  part.add_header("Content-Disposition", f"attachment; filename=NDVI_zzipowany.zip")
                  msg.attach(part)

              try:
                  s = smtplib.SMTP('smtp.gmail.com', 587)
                  s.starttls()
                  s.login(moj_mail, haslo)
                  s.sendmail(moj_mail, klient, msg.as_string())
                  s.quit()
                  fmeobjects.FMELogFile().logMessageString("Mail wyslany poprawnie.", fmeobjects.FME_INFORM)
              except Exception as e:
                  fmeobjects.FMELogFile().logMessageString(f"Blad wysylki: {e}", fmeobjects.FME_ERROR)

              self.pyoutput(feature)
    PYTHONSYMBOL = FeatureProcessor

FME custom transformer ResolveWebConnection

Parameters:
- WEB_CONNECTION =   # "HTTP Authentication" Select a Web Connection

Input (input)
    -> ParameterFetcher
ParameterFetcher
    ATTR_LIST = _WEB_CONNECTION $(WEB_CONNECTION)
    -> PythonCaller
PythonCaller
    NEW_ATTRIBUTES = username password
    PYTHONSOURCE:
      import fme
      import fmeobjects
      from fmeobjects import FMEException
      from fmewebservices import FMENamedConnectionManager

      class FeatureProcessor(object):
          def __init__(self):
              pass

          def input(self, feature):
              conn_name = feature.getAttribute('_WEB_CONNECTION')
              conn = self.get_connection(conn_name)
              feature.setAttribute("username", conn.getUserName())
              feature.setAttribute("password", conn.getPassword())

              self.pyoutput(feature)

          def close(self):
              pass
          def get_connection(self, conn_name):
              """Given the name of a Named Connection, return its object."""
              # TODO: Log messages, including user-facing exception messages,
              #  should be prefixed by the transformer name.
              if not conn_name:
                  raise FMEException("Connection must be specified")
              conn = FMENamedConnectionManager().getNamedConnection(conn_name)
              if not conn:
                  raise FMEException("Connection does not exist")
              return conn
    PYTHONSYMBOL = FeatureProcessor
    -> AttributeRemover
AttributeRemover
    REMOVE_ATTRS = _WEB_CONNECTION
    -> Output (output)
Output (output)

FME custom transformer ZipArchiver
Compresses a file or folder and appends it into the specified zip file.
    The archive name will be the same as the target file name. If a file having the same name as the target file has been archived in the zip file already, the file will not be archived.
    The transformer creates a new zip file when receiving the first file that should be archived into it, if the specified zip file doesn't exist. 
    -----
    Note: This transformer has been basically internationalized with 2016-01-22 update. However, depending on the environment (platform, OS version etc.), file path strings containing Non-ASCII characters still may not be treated correctly. Please test enough if the path strings may contain Non-ASCII characters.
    -----
    Input features will be output through the Output port as-is.
    The transformer creates log features which contain these attributes for each file, and outputs them from the LogSuccess/LogFailure port.
    - Result: "success" if the file was archived successfully, "failure" otherwise.
    - Target File: the target file path.
    - Zip File: the zip file path.
    - Archive Name: the archive name of the target file in the zip file if archived successfully, empty otherwise.
    - Comment: compression ratio if archived successfully, failure reason otherwise.
    ファイルまたはフォルダを圧縮し、指定したzipファイルに追加します。
    アーカイブ名は対象のファイル名と同じになります。対象とするファイルと同じ名前のファイルがすでにzipファイルにアーカイブされていた場合、そのファイルはアーカイブされません。
    指定したzipファイルが存在しない場合、このトランスフォーマーはそれにアーカイブすべき最初のファイルを受け取ったときに新しいzipファイルを作成します。
-----
    注: 2016-01-22 の更新によって、このトランスフォーマーは基本的には国際化されました。しかし、環境（プラットフォームやOSのバージョンなど）によっては、ASCII文字（半角の英数字や記号）以外の文字を含むファイルパス文字列ま、まだ正しく処理されない可能性があります。パス文字列に非ASCII文字が含まれる可能性がある場合は、十分にテストしてください。
-----
    入力フィーチャーはそのままOutputポートから出力されます。
    このトランスフォーマーは、次の属性を持つログフィーチャーをファイルごとに作成し、LogSuccess/LogFailureポートから出力します。
    - Result: ファイルが正常にアーカイブされた場合は"succcess"、そうでない場合は"failure"
    - Target File: 対象のファイルパス
    - Zip File: zipファイルパス
    - Archive Name: アーカイブに成功した場合はzipファイル内でのアーカイブ名、失敗した場合は空文字列
    - Comment: アーカイブに成功した場合は圧縮率、失敗した場合はその理由
Parameters 
    Target File or Folder
    : 
    Specify a file or folder path that should be archived. You can also set a feature attribute value to this parameter.
    If you specify a folder path here, all files under the folder will be archived. In the case, the original directory structure will also be preserved, and the archive name of the file will contain path starting from the specified folder.
    アーカイブするファイルまたはフォルダのパスを指定します。フィーチャーの属性をこのパラメーターに設定することもできます。 
    ここにフォルダのパスを指定した場合は、そのフォルダ以下にある全てのファイルがアーカイブされます。その場合、元のディレクトリ構造も維持され、ファイルのアーカイブ名には、指定されたフォルダから始まるパスが含まれます。
    Destination Zip File
    : 
    Specify a zip file path (*.zip). You can also set a feature attribute value to this parameter.
    If the extension of the specified file path is not "zip", the transformer will add ".zip" to the path automatically. 
    zipファイルパス（*.zip）を指定します。フィーチャーの属性をこのパラメーターに設定することもできます。 
    指定されたパスの拡張子が"zip"でない場合は、そのパスに".zip"を自動的に付加します。
    If Destination Zip File Exists
    :
    If the specified destination zip file exists at the translation starting time, this transformer appends compressed files into the existing zip file, by default. If you set 
    "Remove Existing Zip File"
    to this parameter, this transformer removes the existing zip file once at first, and then appends compressed files into the newly created same name zip file. If you set 
    "Rename Destination Zip File"
    , an suffix will be added to the destination zip file name automatically to differentiate from the existing zip file.
    変換の開始時に指定されたzipファイルが存在する場合、デフォルトでは、このトランスフォーマーは既存のzipファイルに圧縮したファイルを追加します。このパラメーターに 
    "Remove Existing Zip File"
    を設定した場合は、このトランスフォーマーは最初に一回だけ既存のzipファイルを削除してから、新たに作成した同じ名前のzipファイルに圧縮したファイルを追加します。
    "Rename Destination Zip File"
    を設定した場合は、既存のzipファイルと区別するため、出力先のzipファイル名にサフィクスが自動的に付加されます。
    Compression Level (Python 3.7+)
    :
    If FME uses Python 3.7+ when running the workspace, you can control the compression levels with this parameter.
        Level 0 indicates just archiving with no compression.
        In a level between 1-9, less number indicates faster and less compression, greater number indicates slower and more compression. However, the order of the numbers does not always exactly match the order of actual compression levels. Depending on the conditions, 6 could be more compression than 9 for example.
        Currently (in Python 3.7), "Default" is equivalent to level 6, but it may be changed in the future.
    This parameter works only with Python 3.7 or later. If the version of Python interpreter is 3.6 or earlier, this parameter setting will just be ignored. 
    FMEがワークスペースの実行時にPython 3.7以降を使用する場合、このパラメーターによって圧縮レベルを指定できます。
        レベル0は、圧縮せずに単にアーカイブすることを示します。
        1から9の間のレベルは、数値が小さいほど高速で圧縮率が低く、数値が大きいほど低速で圧縮率が高いことを示します。ただし、この順番は必ずしも実際の圧縮率の順番と一致するとは限りません。例えば、条件によっては6が9よりも高い圧縮率となることもあります。
        現在（Python 3.7）は"Default"はレベル6と等価ですが、将来変更されるかもしれません。
    このパラメーターはPython 3.7以降でのみ機能します。 Pythonインタープリターのバージョンが3.6以前の場合、このパラメーター設定は無視されます。

Parameters:
- FILE_PATH =   # Target File or Folder
- ZIP_PATH =   # Destination Zip File
- MODE = APPEND
- COMPRESSION_LEVEL = -1   # 0 (No Compression),0%1,1%2,2%3,3%4,4%5,5%6,6%7,7%8,8%9,9%Default,-1 Compression Level (Python 3.7+)

Input (input)
    -> ParameterFetcher
ParameterFetcher
    ATTR_LIST = __ziparchiver.filepath $(FILE_PATH) __ziparchiver.zippath $(ZIP_PATH) __ziparchiver.mode $(MODE) __ziparchiver.compression_level $(COMPRESSION_LEVEL)
    -> PythonCaller
PythonCaller
    NEW_ATTRIBUTES = __ziparchiver.result
    PYTHONSOURCE:
      # 2015-05-24, Takashi Iijima, Original Implementation
      # 2016-01-22, Takashi Iijima, Refactoring and Internationalizing (Tech Preview)
      # 2018-05-02, Takashi Iijima, Avoided 'divided by 0' error that occurred if the original file size was zero.
      # 2018-07-12, Takashi Iijima, Allow Zip64 by default. Thanks to David R.
      # 2020-01-13, Takashi Iijima, Changed Default Python Interpreter to 3.6+, saved with FME 2017.1.2.1
      # 2020-04-25, Takashi Iijima, Added Compression Level option parameter.

      import fme
      import fmeobjects
      import os, zipfile

      class ZipArchiver(object):
          def __init__(self):
              import platform
              majorVersion = int(platform.python_version_tuple()[0])
              if majorVersion < 3:
                  import locale
                  t = locale.getdefaultlocale()
                  self.encode = lambda s: (s.encode(t[1]) if t else s) if isinstance(s, unicode) else s
              else:
                  self.encode = lambda s: s
              self.logger = fmeobjects.FMELogFile()
              self.zpaths = {} # key: specified zip file path (lower-case), value: treated zip file path in this session

          def input(self, feature):
              try:
                  # Retrieve target file path and zip file path from feature attributes.
                  # If the specified zip file path doesn't end with ".zip", add the extension.
                  regulatePath = lambda path: os.path.abspath(path).replace('\\', '/')
                  fpath = regulatePath(feature.getAttribute('__ziparchiver.filepath'))
                  zpath = regulatePath(feature.getAttribute('__ziparchiver.zippath'))
                  if not zpath.lower().endswith('.zip'):
                      zpath = '%s.zip' % zpath
                  keyPath = zpath.lower()

                  mode = feature.getAttribute('__ziparchiver.mode')
                  if os.path.exists(zpath):
                      if mode == 'REMOVE':
                          if keyPath not in self.zpaths:
                              os.remove(zpath)
                      elif mode == 'RENAME':
                          if keyPath in self.zpaths:
                              zpath = self.zpaths[keyPath]
                          else:
                              format, n = '%s_%d.zip', 1
                              while os.path.exists(format % (zpath[:-4], n)): n += 1
                              zpath = format % (zpath[:-4], n)
                  self.zpaths[keyPath] = zpath

                  # Collect target file paths, including empty directries if "fpath" is a directory.
                  # If specified file/directory doesn't exist, throw an error.
                  root = ''
                  fpaths, dpaths = [], []
                  if os.path.exists(fpath): # fpath is a file
                      root = os.path.split(fpath)[0]
                      if os.path.isfile(fpath):
                          fpaths = [fpath]
                      elif os.listdir(fpath): # fpath is a non-empty directory
                          for dirpath, dirnames, filenames in os.walk(fpath):
                              paths = [os.path.join(dirpath, d) for d in dirnames]
                              dpaths += [regulatePath(path) for path in paths if not os.listdir(path)]
                              fpaths += [regulatePath(os.path.join(dirpath, f)) for f in filenames]
                      else: # fpath is an empty directory
                          dpaths = [fpath]
                  else:
                      raise Exception('specified file doesn\'t exist.')

                  # If destination directory doesn't exist, create the directory.
                  if not os.path.exists(os.path.split(zpath)[0]):
                      os.makedirs(os.path.split(zpath)[0])

                  # Then, perform archiving.
                  # Add "compresslevel" parameter if 3.7 <= Version of Python interpreter.
                  expression = "zipfile.ZipFile(zpath, 'a', zipfile.ZIP_DEFLATED, allowZip64=True"
                  import platform
                  vmajor, vminor, _ = platform.python_version_tuple()
                  if 3 <= int(vmajor) and 7 <= int(vminor):
                      level = feature.getAttribute('__ziparchiver.compression_level')
                      expression = expression + ', compresslevel=%s' % level
                  with eval(expression + ')') as zipper:
                      for path in [path for path in fpaths if path.lower() != zpath.lower()]:
                          aname = path[len(root) + 1:] # archive name
                          result, msg = False, ''
                          try:
                              info = zipper.getinfo(aname)
                              msg = '"%s" exists in the archive already.' % aname
                          except:
                              try:
                                  zipper.write(path, aname)
                                  info = zipper.getinfo(aname)
                                  after = info.compress_size/1024.0
                                  before = info.file_size/1024.0
                                  rate = ('%.1f%%' % (after/before*100.0)) if 0 < before else 'N/A'
                                  msg = '%s (%.1f / %.1f KB)' % (rate, after, before)
                                  result = True
                              except Exception as ex:
                                  msg = '%s' % ex
                          self.outputLogFeature('Success' if result else 'Failure', path, zpath, aname, msg)
                      for path in dpaths:
                          aname = path[len(root) + 1:] # archive name
                          try:
                              info = zipper.getinfo(aname)
                          except:
                              zipper.write(path, aname)
              except Exception as ex:
                  self.outputLogFeature('Terminate', fpath, zpath, '', '%s' % ex)
              finally: # always output the input feature through the Output port.
                  self.pyoutput(feature)

          # Output a log feature.
          def outputLogFeature(self, flag, fpath, zpath, aname, msg):
              if flag != 'Success':
                  self.logger.logMessageString(self.encode('ZipArchiver: %s' % msg), \
                      fmeobjects.FME_ERROR if flag == 'Terminate' else fmeobjects.FME_WARN)
              feature = fmeobjects.FMEFeature()
              feature.setAttribute('__ziparchiver.result', flag.lower())
              feature.setAttribute('Target File', fpath)
              feature.setAttribute('Zip File', zpath)
              feature.setAttribute('Archive Name', aname if flag == 'Success' else '')
              feature.setAttribute('Comment', msg)
              feature.setAttribute('fme_feature_type', 'ZipArchiver_%s' % flag)
              self.pyoutput(feature)
    PYTHONSYMBOL = ZipArchiver
    -> Tester
Tester
    BOOL_OP = OR
    TEST_CLAUSE = TEST __ziparchiver.result ATTRIBUTE_IS_MISSING ""
    TEST_MODE = Automatic
    PASSED -> Output (output)
    FAILED -> AttributeRenamer
Output (output)
AttributeRenamer
    ATTR_LIST = __ziparchiver.result,Result,
    -> AttributeExposer
AttributeExposer
    ATTR_LIST = "Target File","Zip File","Archive Name",Comment
    -> AttributeKeeper
AttributeKeeper
    CREATE_BULK_MODE_FEATURES = NO
    KEEP_ATTRS = Archive Name,Comment,Result,Target File,Zip File
    -> AttributeFilter
AttributeFilter
    ATTR_NAME = Result
    ATTR_VALUES = success,failure,terminate,<EMPTY>,<MISSING>,<NULL>,<UNFILTERED>
    success -> LogSuccess (output)
    failure -> LogFailure (output)
    terminate -> <Rejected> (output)
LogSuccess (output)
LogFailure (output)
<Rejected> (output)

FME custom transformer SentinelDownloader
Description
This transformer allows you to access the COPERNICUS Data Space Ecosystem and download Sentinel-II images right from the source.
Since the existing Sentinel-II reader targets an "Requester pays" Amazon bucket, AWS credentials are required in addition to a charge per x requests or GB.
Using the con terra SentinelDownloader transformer, you only need a free account from COPERNICUS Data Space Ecosystem to access the Sentinel-II data.  Upon creating an account, you have to register an OAuth client, as desribed in here.
If you have any question or if you are looking for professional services support, please contact fme@conterra.de. 
Configuration
Please ensure that you saved the workspace you're using this custom transformer in to a file before using it. The workspace uses referential paths when accessing the downloaded images.
Input Port
Initiator: 
An Area Of Interest (AOI) polygon feature OR 
A point feature (e.g. defined in the Creator transformer)
Coordinates must be in LL84. 
Parameters/Properties
Web Connection:
- Please create an FME Web Connection of type HTTP Authentification and set it up with your credentials (id and secret). It will be used in the workspace to request an access token for the data search and download via COPERNICUS Data Space API.
MOST_RECENT [optional]:
Check if you want only the most recent image of your ingestion period
BEGIN: 
Choose the start date of your ingestion period 
END [optional]: 
Choose the end date of your ingestion period. If not set, the recent date is choosen.
LEVEL: 
Choose between the two data product levels: Level 1C (Top of atmosphere reflectances, geometric and radiometric corrected) and Level 2A (Botton of atmosphere reflectances)
CLOUDCOVER [optional]: 
In this optional parameter, you can choose whether you want your results are filtered by a maximum cloud cover percentage. Keep in mind that this parameter could be the bottleneck of your search query as it possibly will exclude data if the parameter value is too small. 
Output bands: 
Choose between the three possible spatial resolutions (ground sampling distance) 10m, 20m, 60m, or select Download all bands. 
Output Ports
The output depends on the choosen product Level and spatial resolution. For detailed information about a specific band, see this.   
Level 1C:
10m 
Bands 2, 3, 4, and 8. 
20m 
Bands 5, 6, 7, 8A, 11, and 12. 
60m 
Bands 1, 9, and 10 
All 
All 13 bands at their best posible spatial resolution (see above) and the True Color Image (TCI) 
Level 2A:
10m 
Bands 2, 3, 4, 8, and TCI. 
20m
Bands 2, 3, 4, 5, 6, 7, 8A, 11, and 12 + TCI (all bands in 20m spatial resolution) 
60m 
Bands 1, 2, 3, 4, 5, 6, 7, 8A, 9, 11, and 12 + TCI (all bands in 60m spatial resolution) 
All 
All 12 bands at their best posible spatial resolution (see above) and the True Color Image (TCI)

Parameters:
- PARAMETER =   # COPERNICUS Data Space credentials (https://dataspace.copernicus.eu/)
- MSG =
- WEB_CON =   # "HTTP Authentication" Web Connection with client ID and secret
- PARAMETER_2 =   # Search parameters
- MOST_RECENT = NO   # Latest image?
- BEGIN =   # Enter the start date of ingestion
- END =   # Enter the end of your ingestion period
- LEVEL =   # "Level 1C"%"Level 2A" Product Level
- CloudCover = 1   # Enter MAX Cloud Cover Percentage in %
- PARAMETER_4 =   # Output bands
- ALL_BANDS = YES   # Download all bands?
- PARAMETER_5 =   # 10m
- ALL_BANDS_10 = NO   # Download all 10m bands?
- B2_10m = NO   # Band 2 10m
- B3_10m = NO   # Band 3 10m
- B4_10m = NO   # Band 4 10m
- B8_10m = NO   # Band 8 10m
- TCI_10m = NO   # TCI 10m
- PARAMETER_6 =   # 20m
- ALL_BANDS_20 = NO   # Download all 20m bands?
- B2_20m = NO   # Band 2 20m (only with L2A)
- B3_20m = NO   # Band 3 20m (only with L2A)
- B4_20m = NO   # Band 4 20m (only with L2A)
- B5_20m = NO   # Band 5 20m
- B6_20m = NO   # Band 6 20m
- B7_20m = NO   # Band 7 20m
- B8_20m = NO   # Band 8a 20m
- B11_20m = NO   # Band 11 20m
- B12_20m = NO   # Band 12 20m
- TCI_20m = NO   # TCI 20m (only with L2A)
- PARAMETER_7 =   # 60m
- ALL_BANDS_60 = NO   # Download all 60m bands?
- B1_60m = NO   # Band 1 60m
- B2_60m = NO   # Band 2 60m (only with L2A)
- B3_60m = NO   # Band 3 60m (only with L2A)
- B4_60m = NO   # Band 4 60m (only with L2A)
- B5_60m = NO   # Band 5 60m (only with L2A)
- B6_60m = NO   # Band 6 60m (only with L2A)
- B7_60m = NO   # Band 7 60m (only with L2A)
- B8_60m = NO   # Band 8 60m (only with L2A)
- B9_60m = NO   # Band 9 60m
- B11_60m = NO   # Band 11 60m (only with L2A)
- B12_60m = NO   # Band 12 60m (only with L2A)
- TCI_60m = YES   # TCI 60m (only with L2A)

Initiator (input)
    -> CsmapReprojector
CsmapReprojector
    DEST = LL-WGS84
    INTERPOLATION_TYPE_NAME = NearestNeighbor
    RASTER_CELL_SIZE = PreserveCells
    RASTER_TOLERANCE = 0.0
    REPROJECTED -> ParameterFetcher
Junction_5
    -> Junction_3
Junction_3
    -> Junction_4
Junction_4
    -> Junction_2

Bookmark: Create token
ParameterFetcher
    ATTR_LIST = _WEB_CON $(WEB_CON)
    -> ResolveWebConnection
ResolveWebConnection
    WEB_CONNECTION = @Value(_WEB_CON)
    -> AttributeCreator_2
AttributeCreator_2
    ATTR_TABLE = SET_TO enc (varchar(200)) = grant_type=client_credentials&client_id=@Value(username)&client_secret=@Value(password)
    -> HTTPCaller_11
HTTPCaller_11
    CLIENT_CERTIFICATE_TYPE = NONE
    CONNECTION_TIMEOUT_LENGTH = 60
    CONTENT_TYPE_LOOKUP = application/x-www-form-urlencoded
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://identity.dataspace.copernicus.eu/auth/realms/CDSE/protocol/openid-connect/token
    TRANSFER_TIMEOUT_LENGTH = 90
    UPLOAD_BODY = @Value(enc)
    UPLOAD_TYPE = STRING_UPLOAD
    USE_COOKIES = No
    VERIFY_SSL_CERTIFICATES = Yes
    UPLOAD_CONTENT_TYPE = URL Encoded (application/x-www-form-urlencoded)
    -> AttributeRemover_6
    <REJECTED> -> Terminator_6
AttributeRemover_6
    REMOVE_ATTRS = _WEB_CON,enc,password,username
    -> Tester_5
Note: Response code = 200?
Tester_5
    BOOL_OP = OR
    TEST_CLAUSE = TEST @Value(_http_status_code) = 200
    TEST_MODE = TEST
    PASSED -> Logger_6
    FAILED -> Terminator_6
Logger_6
    LOG_FEATURE = NONE
    MAXFEATS = 20
    MESSAGE = Token creation successfull.
    SEVERITY = INFO
    LOGGED -> JSONFlattener_2
JSONFlattener_2
    ERROR_LIST_ATTR = _json_error
    JSON_DOCUMENT = @Value(_response_body)
    NEW_ATTRIBUTES = access_token buffer
    READ_FROM_FILE = NO
    RECURSIVE = YES
    -> AttributeRemover
AttributeRemover
    REMOVE_ATTRS = _encoded,_http_status_code,_response_body
    -> ParameterFetcher_2
ParameterFetcher_2
    ATTR_LIST = _END $(END) _LEVEL $(LEVEL)
    -> GeometryFilter
Note: Token could not be created
Terminator_6
    MESSAGE:
      Token creation failed with response code @Value(_http_status_code)
      Error:
      @Value(fme_rejection_code)
      Response body:
      @Value(_response_body)

Bookmark: Downloading Sentinel-2 data
Note: Is the input geometry a point or an area?
GeometryFilter
    FILTER_MODE = SIMPLE
    FILTER_MULTI = FILTER_TYPES]Point Area]FILTER_TYPES_Simple]Point Area
    FILTER_TYPES = Point Area
    FILTER_TYPES_Simple = Point Area
    Point -> Reprojector
    Area -> BoundingBoxReplacer
    <UNFILTERED> -> Terminator
Note: Only most recent image?
Tester_6
    BOOL_OP = OR
    TEST_CLAUSE = TEST $(MOST_RECENT) = NO
    TEST_MODE = TEST
    PASSED -> AttributeRemover_7
    FAILED -> AttributeCreator_3
Note: Add "top=1" to URL
AttributeCreator_3
    ATTR_TABLE = SET_TO url (varchar(200)) = @Value(url)&$top=1
    -> AttributeRemover_7
AttributeRemover_7
    REMOVE_ATTRS = _END,_geometry,_LEVEL
    -> Logger_7
Logger_7
    LOG_FEATURE = NONE
    MAXFEATS = 20
    MESSAGE = HTTP request against @Value(url) ...
    SEVERITY = INFO
    LOGGED -> HTTPCaller_3
Note: Select based on intersection with Point/Polygon and platformname:Sentinel-2 and ingestion date
HTTPCaller_3
    CLIENT_CERTIFICATE_TYPE = NONE
    CONNECTION_TIMEOUT_LENGTH = 60
    ERROR_ATTR = _error
    FOLLOW_REDIRECTS = FOLLOW_WITH_ORIGINAL_METHOD
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(url)
    TRANSFER_TIMEOUT_LENGTH = 90
    USE_COOKIES = No
    VERIFY_SSL_CERTIFICATES = Yes
    -> AttributeKeeper
    <REJECTED> -> Junction_5
AttributeKeeper
    CREATE_BULK_MODE_FEATURES = NO
    KEEP_ATTRS = _response_body,access_token
    -> JSONFragmenter_4
Note: Terminate the translation if an unexpected input exists
Note: https://catalogue.dataspace.copernicus.eu/odata/v1/Products?&$filter=(startswith(Name,%27S2%27)%20and%20(Attributes/OData.CSC.StringAttribute/any(att:att/Name%20eq%20%27instrumentShortName%27%20and%20att/OData.CSC.StringAttribute/Value%20eq%20%27MSI%27)%20and%20Attributes/OData.CSC.DoubleAttribute/any(att:att/Name%20eq%20%27cloudCover%27%20and%20att/OData.CSC.DoubleAttribute/Value%20le%2022)%20and%20(contains(Name,%27L2A%27)%20and%20OData.CSC.Intersects(area=geography%27SRID=4326;POLYGON%20((7.73%2051.87,%208.08%2051.87,%208.08%2052.07,%207.73%2052.07,%207.73%2051.87))%27)))%20and%20Online%20eq%20true)%20and%20ContentDate/Start%20ge%202023-06-12T00:00:00.000Z%20and%20ContentDate/Start%20lt%202023-06-15T23:59:59.999Z&$orderby=ContentDate/Start%20desc&$expand=Attributes&$count=True&$top=50&$expand=Assets&$skip=0
Terminator
    MESSAGE = Translation Terminated because none of the input parameters was either a point, polygon, or text (WKT) feature.

Bookmark: Spatial filter by point object --> build the OpenSearch URL
Reprojector
    DEST = LL-WGS84
    INTERPOLATION_TYPE = NearestNeighbor
    RASTER_CELL_SIZE = PreserveCells
    RASTER_TOLERANCE = 0.0
    REPROJECTED -> CoordinateExtractor
CoordinateExtractor
    IND = 0
    RECURSIVE = No
    X_ATTR = lon
    Y_ATTR = lat
    MODE = Specify Coordinate
    -> AttributeCreator
AttributeCreator
    ATTR_TABLE:
      SET_TO base_url_S2 (buffer) = https://catalogue.dataspace.copernicus.eu/odata/v1/Products?$filter=
      SET_TO productType (varchar(200)) = FME_CONDITIONAL:DEFAULT_VALUE'Attributes/OData.CSC.StringAttribute/any(att:att/Name eq 'productType' and att/OData.CSC.StringAttribute/Value eq 'S2MSI2A')'BOOL_OP;OR;COMPOSITE_TEST;1;TEST @Value(_LEVEL) = Level 1C'Attributes/OData.CSC.StringAttribute/any(att:att/Name eq 'productType' and att/OData.CSC.StringAttribute/Value eq 'S2MSI1C')'FME_NUM_CONDITIONS2___
      SET_TO cloud_cover (varchar(200)) = Attributes/OData.CSC.DoubleAttribute/any(att:att/Name eq 'cloudCover' and att/OData.CSC.DoubleAttribute/Value lt $(CloudCover))
      SET_TO end_date (varchar(200)) = FME_CONDITIONAL:DEFAULT_VALUE'@Value(_END)'BOOL_OP;OR;COMPOSITE_TEST;1;TEST _END NOT_ATTRIBUTE_HAS_A_VALUE _FME_BLANK_STRING_'@DateTimeFormat(@DateTimeNow(),%Y-%m-%d)'FME_NUM_CONDITIONS2___
      SET_TO daterange (varchar(200)) = ContentDate/Start gt @DateTimeFormat($(BEGIN),%Y-%m-%d)T00:00:00.000Z and ContentDate/Start lt @DateTimeFormat(@Value(end_date),%Y-%m-%d)T00:00:00.000Z
      SET_TO location (varchar(200)) = OData.CSC.Intersects(area=geography%27SRID=4326;POINT(@Value(lon)%20@Value(lat))%27)
      SET_TO url (varchar(200)) = @Value(base_url_S2)@Value(cloud_cover) and @Value(productType) and @Value(daterange) and @Value(location)&$orderby=ContentDate/Start desc
    -> Tester_6

Bookmark: Spatial filter by polygon object --> build the OpenSearch URL
BoundingBoxReplacer
    BBTYPE = BB
    BOXTYPE = 2D Bounding Box
    BOX -> Reprojector_2
Note: Ensure that the CRS is WGS84
Reprojector_2
    DEST = LL-WGS84
    INTERPOLATION_TYPE = NearestNeighbor
    RASTER_CELL_SIZE = PreserveCells
    RASTER_TOLERANCE = 0.0
    REPROJECTED -> GeometryExtractor
GeometryExtractor
    ATTR = _geometry
    KIND = wkt
    OGCVERSION = 1.2
    OGC_WKT_PRECISION = FLOAT_64
    REMOVE_GEOMETRY = No
    KIND_LONG = OGC Well Known Text
    OGC_WKT_PRECISION_DISPLAY = 64-bit
    -> AttributeCreator_6
AttributeCreator_6
    ATTR_TABLE:
      SET_TO base_url_S2 (buffer) = https://catalogue.dataspace.copernicus.eu/odata/v1/Products?$filter=
      SET_TO productType (varchar(200)) = FME_CONDITIONAL:DEFAULT_VALUE'Attributes/OData.CSC.StringAttribute/any(att:att/Name eq 'productType' and att/OData.CSC.StringAttribute/Value eq 'S2MSI2A')'BOOL_OP;OR;COMPOSITE_TEST;1;TEST @Value(_LEVEL) = Level 1C'Attributes/OData.CSC.StringAttribute/any(att:att/Name eq 'productType' and att/OData.CSC.StringAttribute/Value eq 'S2MSI1C')'FME_NUM_CONDITIONS2___
      SET_TO cloud_cover (varchar(200)) = Attributes/OData.CSC.DoubleAttribute/any(att:att/Name eq 'cloudCover' and att/OData.CSC.DoubleAttribute/Value lt $(CloudCover))
      SET_TO end_date (varchar(200)) = FME_CONDITIONAL:DEFAULT_VALUE'@Value(_END)'BOOL_OP;OR;COMPOSITE_TEST;1;TEST _END NOT_ATTRIBUTE_HAS_A_VALUE _FME_BLANK_STRING_'@DateTimeFormat(@DateTimeNow(),%Y-%m-%d)'FME_NUM_CONDITIONS2___
      SET_TO daterange (varchar(200)) = ContentDate/Start gt @DateTimeFormat($(BEGIN),%Y-%m-%d)T00:00:00.000Z and ContentDate/Start lt @DateTimeFormat(@Value(end_date),%Y-%m-%d)T00:00:00.000Z
      SET_TO location (varchar(200)) = OData.CSC.Intersects(area=geography%27SRID=4326;@Value(_geometry)%27)
      SET_TO url (varchar(200)) = @Value(base_url_S2)@Value(cloud_cover) and @Value(productType) and @Value(daterange) and @Value(location)&$orderby=ContentDate/Start desc
    -> Tester_6

Bookmark: Check online status of requested image
Note: Get information from response_body
JSONFragmenter_4
    EXPLODE_FORMAT = JSON
    EXTRACT_ATTR = Yes
    JSON_ATTR = _response_body
    JSON_QUERY = json["value"][*]
    NEW_ATTRIBUTES = Online buffer Id buffer ContentDate.Start buffer
    READ_FROM_FILE = NO
    RECURSIVE = YES
    REJECT_EMPTY_LISTS = YES
    FRAGMENTS -> AttributeRemover_2
    <REJECTED> -> Terminator_2
AttributeRemover_2
    REMOVE_ATTRS = json_index,json_type
    -> Tester_7
Note: Data online?
Tester_7
    BOOL_OP = OR
    TEST_CLAUSE = TEST @Value(Online) = Yes
    TEST_MODE = TEST
    PASSED -> Logger_5
    FAILED -> Logger_4
Logger_5
    LOG_FEATURE = NONE
    MAXFEATS = 20
    MESSAGE = Reqeusted data is ONLINE. Download will be triggered now.
    SEVERITY = WARN
    LOGGED -> Junction
    LOGGED -> AttributeCreator_7
AttributeCreator_7
    ATTR_TABLE = SET_TO nodes_url (varchar(200)) = https://catalogue.dataspace.copernicus.eu/odata/v1/Products(@Value(Id))/Nodes
    -> AttributeRemover_3
Note: Clean up
AttributeRemover_3
    REMOVE_ATTRS = _response_body,Online
    -> HTTPCaller_6
Note: Sentinel data is moved to the archive after a certain period. A download request will trigger the data to be "re-uploaded" to the hub. / --> This is no longer the case. The workflow should stay in the process as it might come back later.
Logger_4
    LOG_FEATURE = NONE
    MAXFEATS = 20
    MESSAGE:
      Reqeusted data is NOT ONLINE. Sentinel's Long Time Archive (LTA) will be triggered now. If successfull, data will be available within hours.
      For further information, see https://scihub.copernicus.eu/userguide/LongTermArchive
    SEVERITY = WARN
    LOGGED -> Junction
    LOGGED -> HTTPCaller_2
Note: Terminate the translation if no results were acquired
Terminator_2
    MESSAGE:
      Translation Terminated. There are zero search results with your parameters.
      To get results, please change the parameters, e.g. the ingestion date or the maximum cloud coverage percentage.

Bookmark: SPATIAL RESOLUTION = Specific bands
Note: https://catalogue.dataspace.copernicus.eu/odata/v1/Products(<productID>)
HTTPCaller_6
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(nodes_url)
    TRANSFER_TIMEOUT_LENGTH = 90
    USE_COOKIES = No
    VERIFY_SSL_CERTIFICATES = Yes
    -> JSONFragmenter_5
JSONFragmenter_5
    EXPLODE_FORMAT = JSON
    EXTRACT_ATTR = Yes
    JSON_ATTR = _response_body
    JSON_QUERY = json["result"][*]
    NEW_ATTRIBUTES = Nodes.uri buffer
    READ_FROM_FILE = NO
    RECURSIVE = YES
    REJECT_EMPTY_LISTS = YES
    FRAGMENTS -> HTTPCaller_12
    <REJECTED> -> Junction_11
HTTPCaller_12
    CLIENT_CERTIFICATE_TYPE = NONE
    CONNECTION_TIMEOUT_LENGTH = 60
    CUSTOM_HEADERS = Authorization;Bearer @Value(access_token)
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(Nodes.uri)(GRANULE)/Nodes
    TRANSFER_TIMEOUT_LENGTH = 90
    USE_COOKIES = No
    VERIFY_SSL_CERTIFICATES = Yes
    -> JSONFragmenter_6
    <REJECTED> -> Junction_3
JSONFragmenter_6
    EXPLODE_FORMAT = JSON
    EXTRACT_ATTR = Yes
    JSON_ATTR = _response_body
    JSON_QUERY = json["result"][*]
    NEW_ATTRIBUTES = Nodes.uri buffer
    READ_FROM_FILE = NO
    RECURSIVE = YES
    REJECT_EMPTY_LISTS = YES
    FRAGMENTS -> HTTPCaller_13
    <REJECTED> -> Junction_11
HTTPCaller_13
    CLIENT_CERTIFICATE_TYPE = NONE
    CONNECTION_TIMEOUT_LENGTH = 60
    CUSTOM_HEADERS = Authorization;Bearer @Value(access_token)
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(Nodes.uri)(IMG_DATA)/Nodes
    TRANSFER_TIMEOUT_LENGTH = 90
    USE_COOKIES = No
    VERIFY_SSL_CERTIFICATES = Yes
    -> AttributeRemover_4
    <REJECTED> -> Junction_4
Note: Clean up
AttributeRemover_4
    REMOVE_ATTRS = Nodes.uri
    -> JSONFragmenter_2
JSONFragmenter_2
    EXPLODE_FORMAT = JSON
    EXTRACT_ATTR = Yes
    JSON_ATTR = _response_body
    JSON_QUERY = json["result"][*]
    NEW_ATTRIBUTES = Id buffer Nodes.uri buffer
    READ_FROM_FILE = NO
    RECURSIVE = YES
    REJECT_EMPTY_LISTS = YES
    FRAGMENTS -> Tester_8
    <REJECTED> -> Junction_9
Note: L2A
Junction_9
    -> Junction_10
Note: Product level? / Level 1C / Level 2A
Tester_8
    BOOL_OP = OR
    TEST_CLAUSE = TEST $(LEVEL) = Level 2A
    TEST_MODE = TEST
    PASSED -> TestFilter_2
    FAILED -> TestFilter_3
Note: Filter choosen bands (L2A)
TestFilter_2
    DEFAULT_VALUE = <UNFILTERED>
    PASSED_TEST_GROUP_OUTPUT = FIRST
    TEST_LIST:
      "BOOL_OP,OR,COMPOSITE_TEST,""""""1"""""",TEST_CLAUSE,TEST $(ALL_BANDS) = YES",All,"BOOL_OP,COMPOSITE,COMPOSITE_TEST,""""""( 1 OR 2 OR 3 OR 4 OR 5 OR 6 ) AND 7"""""",TEST_CLAUSE,TEST $(ALL_BANDS_10) = YES
      TEST $(B2_10m) = YES
      TEST $(B3_10m) = YES
      TEST $(B4_10m) = YES
      TEST $(TCI_10m) = YES
      TEST $(B8_10m) = YES
      TEST @Value(Id) = R10m",10m,"BOOL_OP,COMPOSITE,COMPOSITE_TEST,""""""( 1 OR 2 OR 3 OR 4 OR 5 OR 6 OR 7 OR 8 OR 9 OR 10 OR 11 ) AND 12"""""",TEST_CLAUSE,TEST $(ALL_BANDS_20) = YES
      TEST $(B2_20m) = YES
      TEST $(B3_20m) = YES
      TEST $(B4_20m) = YES
      TEST $(B5_20m) = YES
      TEST $(B6_20m) = YES
      TEST $(B7_20m) = YES
      TEST $(B8_20m) = YES
      TEST $(B11_20m) = YES
      TEST $(B12_20m) = YES
      TEST $(TCI_20m) = YES
      TEST @Value(Id) = R20m",20m,"BOOL_OP,COMPOSITE,COMPOSITE_TEST,""""""( 1 OR 2 OR 3 OR 4 OR 5 OR 6 OR 7 OR 8 OR 9 OR 10 OR 11 OR 12 OR 13 ) AND 14"""""",TEST_CLAUSE,TEST $(ALL_BANDS_60) = YES
      TEST $(B1_60m) = YES
      TEST $(B2_60m) = YES
      TEST $(B3_60m) = YES
      TEST $(B4_60m) = YES
      TEST $(B5_60m) = YES
      TEST $(B6_60m) = YES
      TEST $(B7_60m) = YES
      TEST $(B8_60m) = YES
      TEST $(B9_60m) = YES
      TEST $(B11_60m) = YES
      TEST $(B12_60m) = YES
      TEST $(TCI_60m) = YES
      TEST @Value(Id) = R60m",60m
    All -> AttributeCreator_5
    10m -> AttributeCreator_5
    20m -> AttributeCreator_5
    60m -> AttributeCreator_5
Note: L1C
Note: Filter choosen bands / (L1C)
TestFilter_3
    DEFAULT_VALUE = <UNFILTERED>
    PASSED_TEST_GROUP_OUTPUT = FIRST
    TEST_LIST:
      "BOOL_OP,OR,COMPOSITE_TEST,""""""1"""""",TEST_CLAUSE,TEST $(ALL_BANDS) = YES",All,"BOOL_OP,COMPOSITE,COMPOSITE_TEST,""""""( 1 AND 2 ) OR ( 3 AND 4 ) OR  ( 5 AND 6 ) OR ( 7 AND 8 ) OR ( 9 AND 10 ) OR ( 11 AND 12 )"""""",TEST_CLAUSE,TEST $(ALL_BANDS_10) = YES
      CASE_INSENSITIVE_TEST @Value(Id) CONTAINS_REGEX _(TCI|B0(2|3|4|8)).jp2$
      TEST $(B2_10m) = YES
      CASE_INSENSITIVE_TEST @Value(Id) ENDS_WITH _B02.jp2
      TEST $(B3_10m) = YES
      CASE_INSENSITIVE_TEST @Value(Id) ENDS_WITH _B03.jp2
      TEST $(B4_10m) = YES
      CASE_INSENSITIVE_TEST @Value(Id) ENDS_WITH _B04.jp2
      TEST $(B8_10m) = YES
      CASE_INSENSITIVE_TEST @Value(Id) ENDS_WITH _B08.jp2
      TEST $(TCI_10m) = YES
      CASE_INSENSITIVE_TEST @Value(Id) ENDS_WITH _TCI.jp2",Bands 2 download,"BOOL_OP,COMPOSITE,COMPOSITE_TEST,""""""( 1 AND 2 ) OR ( 3 AND 4 ) OR  ( 5 AND 6 ) OR ( 7 AND 8 ) OR ( 9 AND 10 ) OR ( 11 AND 12 ) OR ( 13 AND 14 )"""""",TEST_CLAUSE,TEST $(ALL_BANDS_20) = YES
      CASE_INSENSITIVE_TEST @Value(Id) CONTAINS_REGEX _(B8A|B0(5|6||8)|B1(1|2)).jp2$
      TEST $(B5_20m) = YES
      CASE_INSENSITIVE_TEST @Value(Id) ENDS_WITH _B05.jp2
      TEST $(B6_20m) = YES
      CASE_INSENSITIVE_TEST @Value(Id) ENDS_WITH _B06.jp2
      TEST $(B7_20m) = YES
      CASE_INSENSITIVE_TEST @Value(Id) ENDS_WITH _B07.jp2
      TEST $(B8_20m) = YES
      CASE_INSENSITIVE_TEST @Value(Id) ENDS_WITH _B8A.jp2
      TEST $(B11_20m) = YES
      CASE_INSENSITIVE_TEST @Value(Id) ENDS_WITH _B11.jp2
      TEST $(B12_20m) = YES
      CASE_INSENSITIVE_TEST @Value(Id) ENDS_WITH _B12.jp2",Bands 2 download,"BOOL_OP,COMPOSITE,COMPOSITE_TEST,""""""( 1 AND 2 ) OR ( 3 AND 4 ) OR  ( 5 AND 6 )"""""",TEST_CLAUSE,TEST $(ALL_BANDS_60) = YES
      CASE_INSENSITIVE_TEST @Value(Id) CONTAINS_REGEX _(B10|B0(1|9)).jp2$
      TEST $(B1_60m) = YES
      CASE_INSENSITIVE_TEST @Value(Id) ENDS_WITH _B01.jp2
      TEST $(B9_60m) = YES
      CASE_INSENSITIVE_TEST @Value(Id) ENDS_WITH _B09.jp2",Bands 2 download
    All -> StringReplacer
    Bands 2 download -> StringReplacer
Note: replace /Nodes for download link
StringReplacer
    CASE = NO
    FIND_TEXT = /Nodes$
    NO_MATCH = _FME_NO_OP_
    REGEXP = YES
    REPLACE_TEXT = /$value
    SRC_ATTRS = Nodes.uri
    -> AttributeKeeper_5
Note: Clean up data
AttributeKeeper_5
    CREATE_BULK_MODE_FEATURES = NO
    KEEP_ATTRS = Id,Nodes.uri,access_token
    -> HTTPCaller_10
Note: Download data
HTTPCaller_10
    CLIENT_CERTIFICATE_TYPE = NONE
    CONNECTION_TIMEOUT_LENGTH = 60
    CUSTOM_HEADERS = Authorization;Bearer @Value(access_token)
    ERROR_ATTR = _error
    FILE_PATH_ATTR = _response_file_path
    FOLLOW_REDIRECTS = FOLLOW_WITH_ORIGINAL_METHOD
    HTTP_METHOD = GET
    MAX_HTTP_VERSION = HTTP_2
    MAX_TRANSFERS_IN_PROGRESS = 2
    MINIMUM_ENCRYPTION_LEVEL = OS_DEFAULT
    OUTPUT_FILENAME = @Value(Id)
    REDIRECT_AUTH = ORIGINAL_DOMAIN_ONLY
    RESPONSE_TYPE = File
    STATUS_CODE_ATTR = _http_status_code
    TARGET_URL = @Value(Nodes.uri)
    TRANSFER_TIMEOUT_LENGTH = 90
    USE_COOKIES = No
    VERIFY_SSL_CERTIFICATES = Yes
    -> FeatureHolder_3
    <REJECTED> -> Junction_2
Note: Download all first so that the token does not become invalid
FeatureHolder_3
    -> FeatureReader_2 [INITIATOR]
Junction_11
    -> Junction_12
Junction_12
    -> Junction_13
Junction
    -> StatisticsCalculator

Bookmark: Error catching
Junction_10
    -> Junction_6
Junction_8
    -> Junction_6
Junction_2
    -> FeatureHolder
FeatureHolder
    -> AttributeManager
AttributeManager
    ATTR_TABLE:
      REMOVE Id (buffer)
      REMOVE _response_file_path (buffer)
      REMOVE nodes_url (varchar(200))
      REMOVE image_identifier (buffer)
      REMOVE json_type (buffer)
      REMOVE json_index (uint32)
      REMOVE access_token (buffer)
      REMOVE ContentDate.Start (buffer)
      REMOVE Nodes.uri (buffer)
      REMOVE base_url_S2 (buffer)
      REMOVE productType (varchar(200))
      REMOVE cloud_cover (varchar(200))
      REMOVE daterange (varchar(200))
      REMOVE location (varchar(200))
      REMOVE url (varchar(200))
      REMOVE lon (real64)
      REMOVE lat (real64)
    -> Terminator_4
Terminator_4
    MESSAGE:
      Error at requesting the REST API.
      HTTP Code: @Value(_http_status_code)
      Error: @Value(_error)
Junction_13
    -> Junction_6
Junction_6
    -> FeatureHolder_2
FeatureHolder_2
    -> AttributeManager_2
AttributeManager_2
    ATTR_TABLE:
      REMOVE _response_body (buffer)
      REMOVE _http_status_code (buffer)
      REMOVE nodes_url (varchar(200))
      REMOVE image_identifier (buffer)
      REMOVE json_type (buffer)
      REMOVE json_index (uint32)
      REMOVE Id (buffer)
      REMOVE access_token (buffer)
      REMOVE ContentDate.Start (buffer)
      REMOVE Nodes.uri (buffer)
    -> Terminator_5
Terminator_5
    MESSAGE:
      Error at parsing the response JSON.
      FME rejection code: @Value(fme_rejection_code)

Bookmark: Special handling L2A
AttributeCreator_5
    ATTR_TABLE = SET_TO image_identifier (buffer) = @Value(Nodes.uri)
    -> HTTPCaller_8
Note: Get download links for bands
HTTPCaller_8
    CLIENT_CERTIFICATE_TYPE = NONE
    CONNECTION_TIMEOUT_LENGTH = 60
    CUSTOM_HEADERS = Authorization;Bearer @Value(access_token)
    ERROR_ATTR = _error
    FOLLOW_REDIRECTS = FOLLOW_WITH_ORIGINAL_METHOD
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    RETRY_FAILED_TRANSFERS = CONNECTION 429 500 501 502 503 504 505 506 507 508 509 510 511
    RETRY_INITIAL_BACKOFF = 500
    RETRY_MAX_RETRIES = 3
    SPLIT_MULTIPART_DOWNLOADS = NO
    STATUS_CODE_ATTR = _http_status_code
    TARGET_ATTR = _response_body
    TARGET_ATTR_ENCODING = auto-detect
    TARGET_URL = @Value(image_identifier)
    TRANSFER_TIMEOUT_LENGTH = 90
    USE_COOKIES = No
    VERIFY_SSL_CERTIFICATES = Yes
    -> JSONFragmenter_3
    <REJECTED> -> Junction_2
JSONFragmenter_3
    EXPLODE_FORMAT = JSON
    EXTRACT_ATTR = Yes
    JSON_ATTR = _response_body
    JSON_QUERY = json["result"][*]
    NEW_ATTRIBUTES = Id buffer Nodes.uri buffer
    READ_FROM_FILE = NO
    RECURSIVE = YES
    REJECT_EMPTY_LISTS = YES
    FRAGMENTS -> Tester_4
    <REJECTED> -> Junction_7
Note: Filter AOT and WVP
Tester_4
    BOOL_OP = COMPOSITE
    COMPOSITE_TEST = 1 AND 2 AND 3
    TEST_CLAUSE:
      CASE_INSENSITIVE_TEST @Value(Id) NOT_CONTAINS _AOT_
      CASE_INSENSITIVE_TEST @Value(Id) NOT_CONTAINS _WVP_
      CASE_INSENSITIVE_TEST @Value(Id) NOT_CONTAINS _SCL_
    TEST_MODE = CASE_INSENSITIVE_TEST
    PASSED -> TestFilter
TestFilter
    DEFAULT_VALUE = <UNFILTERED>
    PASSED_TEST_GROUP_OUTPUT = FIRST
    TEST_LIST:
      "BOOL_OP,COMPOSITE,COMPOSITE_TEST,""""""1 AND ( 2 OR 3 OR 4 OR 5 OR 6 OR 7 OR 8 OR 9 OR 10 OR 11 OR 12 OR 13 )"""""",TEST_CLAUSE,TEST $(ALL_BANDS) = YES
      CASE_INSENSITIVE_TEST @Value(Id) ENDS_WITH B01_20m.jp2
      CASE_INSENSITIVE_TEST @Value(Id) ENDS_WITH B02_10m.jp2
      CASE_INSENSITIVE_TEST @Value(Id) ENDS_WITH B03_10m.jp2
      CASE_INSENSITIVE_TEST @Value(Id) ENDS_WITH B04_10m.jp2
      CASE_INSENSITIVE_TEST @Value(Id) ENDS_WITH B05_20m.jp2
      CASE_INSENSITIVE_TEST @Value(Id) ENDS_WITH B06_20m.jp2
      CASE_INSENSITIVE_TEST @Value(Id) ENDS_WITH B07_20m.jp2
      CASE_INSENSITIVE_TEST @Value(Id) ENDS_WITH B08_10m.jp2
      CASE_INSENSITIVE_TEST @Value(Id) ENDS_WITH B09_60m.jp2
      CASE_INSENSITIVE_TEST @Value(Id) ENDS_WITH B11_20m.jp2
      CASE_INSENSITIVE_TEST @Value(Id) ENDS_WITH B12_20m.jp2
      CASE_INSENSITIVE_TEST @Value(Id) ENDS_WITH TCI_10m.jp2",ALL option,"BOOL_OP,COMPOSITE,COMPOSITE_TEST,""""""( 1 AND 2 ) OR ( 3 AND 4 ) OR ( 5 AND 6 ) OR ( 7 AND 8 ) OR ( 9 AND 10 ) OR ( 11 AND 12 )"""""",TEST_CLAUSE,CASE_INSENSITIVE_TEST $(ALL_BANDS_10) = YES
      CASE_INSENSITIVE_TEST @Value(Id) ENDS_WITH _10m.jp2
      CASE_INSENSITIVE_TEST $(B2_10m) = YES
      CASE_INSENSITIVE_TEST @Value(Id) ENDS_WITH _B02_10m.jp2
      CASE_INSENSITIVE_TEST $(B3_10m) = YES
      CASE_INSENSITIVE_TEST @Value(Id) ENDS_WITH _B03_10m.jp2
      CASE_INSENSITIVE_TEST $(B4_10m) = YES
      CASE_INSENSITIVE_TEST @Value(Id) ENDS_WITH _B04_10m.jp2
      CASE_INSENSITIVE_TEST $(B8_10m) = YES
      CASE_INSENSITIVE_TEST @Value(Id) ENDS_WITH _B08_10m.jp2
      CASE_INSENSITIVE_TEST $(TCI_10m) = YES
      CASE_INSENSITIVE_TEST @Value(Id) ENDS_WITH _TCI_10m.jp2",Bands 2 download,"BOOL_OP,COMPOSITE,COMPOSITE_TEST,""""""( 1 AND 2 ) OR ( 3 AND 4 ) OR ( 5 AND 6 ) OR ( 7 AND 8 ) OR ( 9 AND 10 ) OR ( 11 AND 12 ) OR ( 13 AND 14 ) OR ( 15 AND 16 ) OR ( 17 AND 18 ) OR ( 19 AND 20 ) OR ( 21 AND 22 )"""""",TEST_CLAUSE,CASE_INSENSITIVE_TEST $(ALL_BANDS_20) = YES
      CASE_INSENSITIVE_TEST @Value(Id) ENDS_WITH _20m.jp2
      CASE_INSENSITIVE_TEST $(B2_20m) = YES
      CASE_INSENSITIVE_TEST @Value(Id) ENDS_WITH _B02_20m.jp2
      CASE_INSENSITIVE_TEST $(B3_20m) = YES
      CASE_INSENSITIVE_TEST @Value(Id) ENDS_WITH _B03_20m.jp2
      CASE_INSENSITIVE_TEST $(B4_20m) = YES
      CASE_INSENSITIVE_TEST @Value(Id) ENDS_WITH _B04_20m.jp2
      CASE_INSENSITIVE_TEST $(B5_20m) = YES
      CASE_INSENSITIVE_TEST @Value(Id) ENDS_WITH _B05_20m.jp2
      CASE_INSENSITIVE_TEST $(B6_20m) = YES
      CASE_INSENSITIVE_TEST @Value(Id) ENDS_WITH _B06_20m.jp2
      CASE_INSENSITIVE_TEST $(B7_20m) = YES
      CASE_INSENSITIVE_TEST @Value(Id) ENDS_WITH _B07_20m.jp2
      CASE_INSENSITIVE_TEST $(B8_20m) = YES
      CASE_INSENSITIVE_TEST @Value(Id) ENDS_WITH _B8A_20m.jp2
      CASE_INSENSITIVE_TEST $(B11_20m) = YES
      CASE_INSENSITIVE_TEST @Value(Id) ENDS_WITH _B11_20m.jp2
      CASE_INSENSITIVE_TEST $(B12_20m) = YES
      CASE_INSENSITIVE_TEST @Value(Id) ENDS_WITH _B12_20m.jp2
      CASE_INSENSITIVE_TEST $(TCI_20m) = YES
      CASE_INSENSITIVE_TEST @Value(Id) ENDS_WITH _TCI_20m.jp2",Bands 2 download,"BOOL_OP,COMPOSITE,COMPOSITE_TEST,""""""( 1 AND 2 ) OR ( 3 AND 4 ) OR ( 5 AND 6 ) OR ( 7 AND 8 ) OR ( 9 AND 10 ) OR ( 11 AND 12 ) OR ( 13 AND 14 ) OR ( 15 AND 16 ) OR ( 17 AND 18 ) OR ( 19 AND 20 ) OR ( 21 AND 22 ) OR ( 23 AND 24 )"""""",TEST_CLAUSE,CASE_INSENSITIVE_TEST $(B1_60m) = YES
      CASE_INSENSITIVE_TEST @Value(Id) ENDS_WITH _60m.jp2
      CASE_INSENSITIVE_TEST $(B2_60m) = YES
      CASE_INSENSITIVE_TEST @Value(Id) ENDS_WITH _B02_60m.jp2
      CASE_INSENSITIVE_TEST $(B3_60m) = YES
      CASE_INSENSITIVE_TEST @Value(Id) ENDS_WITH _B03_60m.jp2
      CASE_INSENSITIVE_TEST $(B4_60m) = YES
      CASE_INSENSITIVE_TEST @Value(Id) ENDS_WITH _B04_60m.jp2
      CASE_INSENSITIVE_TEST $(B5_60m) = YES
      CASE_INSENSITIVE_TEST @Value(Id) ENDS_WITH _B05_60m.jp2
      CASE_INSENSITIVE_TEST $(B6_60m) = YES
      CASE_INSENSITIVE_TEST @Value(Id) ENDS_WITH _B06_60m.jp2
      CASE_INSENSITIVE_TEST $(B7_60m) = YES
      CASE_INSENSITIVE_TEST @Value(Id) ENDS_WITH _B07_60m.jp2
      CASE_INSENSITIVE_TEST $(B8_60m) = YES
      CASE_INSENSITIVE_TEST @Value(Id) ENDS_WITH _B8A_60m.jp2
      CASE_INSENSITIVE_TEST $(B9_60m) = YES
      CASE_INSENSITIVE_TEST @Value(Id) ENDS_WITH _B09_60m.jp2
      CASE_INSENSITIVE_TEST $(B11_60m) = YES
      CASE_INSENSITIVE_TEST @Value(Id) ENDS_WITH _B11_60m.jp2
      CASE_INSENSITIVE_TEST $(B12_60m) = YES
      CASE_INSENSITIVE_TEST @Value(Id) ENDS_WITH _B12_60m.jp2
      CASE_INSENSITIVE_TEST $(TCI_60m) = YES
      CASE_INSENSITIVE_TEST @Value(Id) ENDS_WITH _TCI_60m.jp2",Bands 2 download
    ALL option -> StringReplacer
    Bands 2 download -> StringReplacer
Junction_7
    -> Junction_8

Bookmark: Read in Sentinel-Images
FeatureReader_2
    ATTRIBUTES = JPEG2000,fme_basename
    ATTR_ACCUM_MODE = Merge Initiator and Result
    ATTR_CONFLICT_RES = Use Result
    ATTR_IGNORE_NULLS = No
    CLIP_TO_ENVELOPE = NO
    COMBINE_GEOM = Use Result
    DATASET = @Value(_response_file_path)
    FEATURETYPES = JPEG2000
    FORMAT = JPEG2000
    INITIATOR_FIRST_OUTPUT = default
    INTERACT = NONE
    JPEG2000_COMPRESSION_CACHE_SIZE_CALCULATION = AUTO
    JPEG2000_GROUP_BY_DATASET = No
    JPEG2000_JPEG2000_EXPOSE_FORMAT_ATTRS = fme_basename,char(50)
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    JPEG2000 -> AttributeRemover_5
AttributeRemover_5
    REMOVE_ATTRS = Id,Nodes.uri,_http_status_code,_response_file_path,access_token
    -> TestFilter_4
TestFilter_4
    DEFAULT_VALUE = <UNFILTERED>
    PASSED_TEST_GROUP_OUTPUT = FIRST
    TEST_LIST = "BOOL_OP,OR,COMPOSITE_TEST,""""""1"""""",TEST_CLAUSE,CASE_SENSITIVE_TEST @Value(fme_basename) CONTAINS_REGEX B01",B01,"BOOL_OP,OR,COMPOSITE_TEST,""""""1"""""",TEST_CLAUSE,CASE_SENSITIVE_TEST @Value(fme_basename) CONTAINS_REGEX B02",B02,"BOOL_OP,OR,COMPOSITE_TEST,""""""1"""""",TEST_CLAUSE,CASE_SENSITIVE_TEST @Value(fme_basename) CONTAINS_REGEX B03",B03,"BOOL_OP,OR,COMPOSITE_TEST,""""""1"""""",TEST_CLAUSE,CASE_SENSITIVE_TEST @Value(fme_basename) CONTAINS_REGEX B04",B04,"BOOL_OP,OR,COMPOSITE_TEST,""""""1"""""",TEST_CLAUSE,CASE_SENSITIVE_TEST @Value(fme_basename) CONTAINS_REGEX B05",B05,"BOOL_OP,OR,COMPOSITE_TEST,""""""1"""""",TEST_CLAUSE,CASE_SENSITIVE_TEST @Value(fme_basename) CONTAINS_REGEX B06",B06,"BOOL_OP,OR,COMPOSITE_TEST,""""""1"""""",TEST_CLAUSE,CASE_SENSITIVE_TEST @Value(fme_basename) CONTAINS_REGEX B07",B07,"BOOL_OP,OR,COMPOSITE_TEST,""""""1"""""",TEST_CLAUSE,CASE_SENSITIVE_TEST @Value(fme_basename) CONTAINS_REGEX B08",B08,"BOOL_OP,OR,COMPOSITE_TEST,""""""1"""""",TEST_CLAUSE,CASE_SENSITIVE_TEST @Value(fme_basename) CONTAINS_REGEX B8A",B8A,"BOOL_OP,OR,COMPOSITE_TEST,""""""1"""""",TEST_CLAUSE,CASE_SENSITIVE_TEST @Value(fme_basename) CONTAINS_REGEX B09",B09,"BOOL_OP,OR,COMPOSITE_TEST,""""""1"""""",TEST_CLAUSE,CASE_SENSITIVE_TEST @Value(fme_basename) CONTAINS_REGEX B10",B10,"BOOL_OP,OR,COMPOSITE_TEST,""""""1"""""",TEST_CLAUSE,CASE_SENSITIVE_TEST @Value(fme_basename) CONTAINS_REGEX B11",B11,"BOOL_OP,OR,COMPOSITE_TEST,""""""1"""""",TEST_CLAUSE,CASE_SENSITIVE_TEST @Value(fme_basename) CONTAINS_REGEX B12",B12,"BOOL_OP,OR,COMPOSITE_TEST,""""""1"""""",TEST_CLAUSE,CASE_SENSITIVE_TEST @Value(fme_basename) CONTAINS_REGEX TCI",TCI
    B01 -> B01 (output)
    B02 -> B02 (output)
    B03 -> B03 (output)
    B04 -> B04 (output)
    B05 -> B05 (output)
    B06 -> B06 (output)
    B07 -> B07 (output)
    B08 -> B08 (output)
    B8A -> B8A (output)
    B09 -> B09 (output)
    B11 -> B11 (output)
    B12 -> B12 (output)
    TCI -> TCI (output)
B01 (output)
B02 (output)
B03 (output)
B04 (output)
B05 (output)
B06 (output)
B07 (output)
B08 (output)
B8A (output)
B09 (output)
B11 (output)
B12 (output)
TCI (output)

Bookmark: Write information to log file
StatisticsCalculator
    ATTR_ACCUM_MODE = None
    CALCULATION_MODE = NUMERIC
    FEAT_STATS = ContentDate.Start,NUMERIC_MODE,,,COUNT,,,,,,,,,,
    PREPEND_ATTR_NAME_OBS = No
    STATISTIC_SUFFIX_RENAME_MAP = COUNT,_count
    SUMMARY -> FeatureMerger [REQUESTOR]
    COMPLETE -> ListBuilder
ListBuilder
    LIST_ATTRS_TO_INCLUDE = ContentDate.Start
    LIST_NAME = _datelist
    -> ListConcatenator
ListConcatenator
    DROP_EMPTY_PARTS = No
    LIST_ATTR = _datelist{}.ContentDate.Start
    SEP = " & "
    VAL_ATTR = _concatenated
    -> FeatureMerger [SUPPLIER]
FeatureMerger
    ATTR_ACCUM_MODE = Merge Supplier
    ATTR_CONFLICT_RES_LOOKUP = REQUESTOR_IF_CONFLICT
    CLEANING_TOLERANCE_LOOKUP = NONE
    CONNECT_Z_MODE_LOOKUP = FIRST_WINS
    GEOM_TYPE_VAL = POLYGONS
    IGNORE_NULLS = No
    JOIN_KEYS = 1 1 AUTO
    MERGE_TYPE_VAL = ATTRIBUTES
    PROCESS_DUPS = YES
    REJECT_NULL_MISSING_KEYS = No
    SUPPLIERS_FIRST = No
    ATTR_CONFLICT_RES = Use Requestor
    CLEANING_TOLERANCE = None
    CONNECT_Z_MODE = First Wins
    GEOM_TYPE = Build Polygons
    MERGE_TYPE = Attributes Only
    MERGED -> Logger
Logger
    LOG_FEATURE = NONE
    MAXFEATS = 100
    MESSAGE:
      Your request delivers @Value(_count) result(s).
      The request delivers images at the following dates: @Value(_concatenated)
    SEVERITY = INFO

Bookmark: Messaging in log file for retrieving of offline data
Note: Trigger ex-archiving
HTTPCaller_2 [off]
    CLIENT_CERTIFICATE_TYPE = NONE
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(download_url)
    TRANSFER_TIMEOUT_LENGTH = 90
    USE_COOKIES = No
    VERIFY_SSL_CERTIFICATES = Yes
    -> Tester [off]
Tester [off]
    BOOL_OP = OR
    TEST_CLAUSE = TEST @Value(_http_status_code) = 202
    TEST_MODE = TEST
    PASSED -> Logger_2 [off]
    FAILED -> AttributeCreator_4 [off]
Logger_2 [off]
    LOG_FEATURE = NONE
    MAXFEATS = 20
    MESSAGE = Retrieval of offline data is triggered successfully. Please try again in a few hours.
    SEVERITY = WARN
AttributeCreator_4 [off]
    ATTR_TABLE = SET_TO error_msg (varchar(200)) = FME_CONDITIONAL:DEFAULT_VALUE'_FME_NO_OP_'BOOL_OP;OR;COMPOSITE_TEST;1;TEST @Value(_http_status_code) = 503'Service unavailable. LTA cannot accept new requests right now. Try again soon.'BOOL_OP;OR;COMPOSITE_TEST;1;TEST @Value(_http_status_code) = 403'Request forbidden. Number of submissions exceeds allowed user quota.'BOOL_OP;OR;COMPOSITE_TEST;1;TEST @Value(_http_status_code) = 500'Internal server error.'FME_NUM_CONDITIONS4___
    -> Logger_3 [off]
Logger_3 [off]
    LOG_FEATURE = NONE
    MAXFEATS = 20
    MESSAGE = @Value(error_msg)
    SEVERITY = ERROR
