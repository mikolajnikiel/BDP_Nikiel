FME workspace BDP12.fmw

Parameters:
- SourceDataset_SHAPEFILE = C:\Users\nikie\Downloads\Karlsruhe_Germany_Shapefile\T2019_KAR_GERMANY\T2019_KAR_POI_TABLE.shp   # Source Esri Shapefile(s)
- SourceDataset_SHAPEFILE_5 = C:\Users\nikie\Downloads\Karlsruhe_Germany_Shapefile\T2019_KAR_GERMANY\T2019_KAR_STREET_NODE.shp   # Source Esri Shapefile(s)
- SourceDataset_SHAPEFILE_4 = C:\Users\nikie\Downloads\Karlsruhe_Germany_Shapefile\T2019_KAR_GERMANY\T2019_KAR_STREETS.shp   # Source Esri Shapefile(s)

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_4)

T2019_KAR_POI_TABLE (reader SHAPEFILE_1)
    attributes: POI_ID long, LINK_ID long, TYPE varchar(250), POI_NAME varchar(250), ST_NAME varchar(250), LAT number(31,15), LON number(31,15)
    -> Reprojector
T2019_KAR_STREET_NODE (reader SHAPEFILE_2)
    attributes: NODE_ID long, LINK_ID long, POINT_NUM long, Z_LEVEL long, INTERSECT varchar(1), LAT number(31,15), LON number(31,15)
    -> Reprojector
T2019_KAR_STREETS (reader SHAPEFILE_3)
    attributes: LINK_ID long, ST_NAME varchar(254), REF_IN_ID long, NREF_IN_ID long, FUNC_CLASS varchar(1), SPEED_CAT varchar(1), FR_SPEED_L long, TO_SPEED_L long, DIR_TRAVEL varchar(1)
    -> Reprojector
Reprojector
    DEST = LL-WGS84
    INTERPOLATION_TYPE = NearestNeighbor
    RASTER_CELL_SIZE = PreserveCells
    RASTER_TOLERANCE = 0.0
